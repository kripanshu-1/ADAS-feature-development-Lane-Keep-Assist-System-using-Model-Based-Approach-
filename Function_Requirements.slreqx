# Function_Requirements

## #1: Stateflow LKA Initialization (Functional)
These requirements are for the initialization of Lane Keep Assist (LKA).

### 1.a: LKA Initialization Conditions (Functional)
LKA initializes when LKA Enable state is selected, Perception module can detect and identify the lanes.

### 1.b: LKA Init for Lane Departure (Functional)
When lane departure warning displays, LKA should be initalize again after 1.2 sec.

## 2: Stateflow LKA Activitation (Functional)
This requirement is for the LKA active state.

### 2.a: LKA in Active State (Functional)
LKA should be active when the sum of lateral offset and orientation error is less than half of lane width.

## 3: Stateflow Lane Departure Warning (Functional)
These requirements are for the Lane Deoparture Warninig state.

### 3.a: Display Lane Departure Warning (Functional)
Lane Departure Warning (LDW) should be displayed when the sum of lateral offset and orientation error is more than half of lane width.

### 3.b: LDW for excess acceleration (Functional)
Lane Departure Warning (LDW) should be displayed when SV lateral acceleration crosses the defined threshold acceleration value.

## 4: Stateflow Driver Control (Functional)
These requiremnets are for the giving control to the driver (Driver Control state) under different conditions.

### 4.a: LKA Disable (Functional)
Ego Vehicle should give control to the driver (driver control state), when LKA Mode is disabled.

### 4.b: No Detection (Functional)
Ego Vehicle should give control to the driver (driver control state), when perception module can not detect and identify the lanes.

## 5: Stanley Controller (Functional)

### 5.a: Steering Angle (Functional)
Steering angle for the lane to be followed.

## 6: MPC (Functional)

### 6.a: Throttle (Functional)
Throttle for the lane to be followed.

### 6.b: Brake (Functional)
Brake when the lane departure selected to follow the lane.
